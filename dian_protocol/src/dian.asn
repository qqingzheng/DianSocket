DianProtocol DEFINITIONS ::= BEGIN


DianConnectionRequest ::= SEQUENCE {  -- 连接服务器请求
    userIdentity    User-Identity
}

DianConnectionResp ::= SEQUENCE {      -- 连接请求回复
    userIdentity    User-Identity,
    respType        Response-Type,
    denyReason      Deny-Reason      OPTIONAL,
    helloMsg        Message          OPTIONAL
}

DianSendMsg ::= SEQUENCE {            -- 向服务器发送信息
    userIdentity    User-Identity,
    msg             Message
}

DianMsgBroadcast ::= SEQUENCE {       -- 服务器广播信息
    msg             Message
}

DianServerClosing ::= SEQUENCE {      -- 服务器关闭广播信息
    exitMsg         Message
}

User-Identity ::=  INTEGER
Response-Type ::=  ENUMERATED {accept, deny, unknown}
Deny-Reason   ::=  ENUMERATED {identityrepeated, unknown}
Message       ::=  PrintableString

END
